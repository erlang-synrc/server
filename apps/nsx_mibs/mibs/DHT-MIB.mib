DHT-MIB DEFINITIONS ::= BEGIN

IMPORTS
    OBJECT-TYPE
	FROM SNMPv2-SMI
    RowStatus
	FROM STANDARD-MIB
    kakaSquares
	FROM SYNRC-REG;

dht OBJECT IDENTIFIER ::= { kakaSquares 1}

dhtArray OBJECT-TYPE
    SYNTAX SEQUENCE OF DHTArrayEntry
    ACCESS not-accessible
    STATUS mandatory
    DESCRIPTION "Table of servers DHT information."
    ::= { dht 1 }

dhtArrayEntry OBJECT-TYPE
    SYNTAX DHTArrayEntry
    ACCESS not-accessible
    STATUS mandatory
    DESCRIPTION        "An entry in dhtTable"
    INDEX   { arrayIndex }    ::= { dhtArray 1 }

DHTArrayEntry ::= SEQUENCE {
    arrayIndex INTEGER,
    value INTEGER,
    dhtStatus2 RowStatus
    }

arrayIndex OBJECT-TYPE
    SYNTAX INTEGER
    ACCESS read-only
    STATUS mandatory
    DESCRIPTION "Server name. Used as index for dhtArray."
    ::= { dhtArrayEntry 1 }

value OBJECT-TYPE
    SYNTAX INTEGER
    ACCESS read-only
    STATUS mandatory
    DESCRIPTION "Server name. Used as index for dhtArray."
    ::= { dhtArrayEntry 2 }

dhtStatus2 OBJECT-TYPE
    SYNTAX RowStatus
    ACCESS  read-write
    STATUS  mandatory
    DESCRIPTION "The status of this row."
    ::= { dhtArrayEntry 3 }

dhtTable OBJECT-TYPE
    SYNTAX SEQUENCE OF DHTEntry
    ACCESS not-accessible
    STATUS mandatory
    DESCRIPTION "Table of servers DHT information."
    ::= { dht 2 }

dhtEntry OBJECT-TYPE
    SYNTAX DHTEntry
    ACCESS not-accessible
    STATUS mandatory
    DESCRIPTION        "An entry in dhtTable"
    INDEX   { dhtIndex }    ::= { dhtTable 1 }


DHTEntry ::= SEQUENCE {
    dhtIndex INTEGER,
    handoffTimeouts INTEGER,
    nodeGetsTotal INTEGER,
    nodePutsTotal INTEGER,
    cpuAvg15 INTEGER,
    nodeGetFsmTimeMedian OCTET STRING,
    nodePutFsmTimeMedian OCTET STRING,
    dhtStatus RowStatus}

dhtIndex OBJECT-TYPE
    SYNTAX INTEGER
    ACCESS read-only
    STATUS mandatory
    DESCRIPTION "Index for dhtTable."
    ::= { dhtEntry 1 }


handoffTimeouts OBJECT-TYPE
    SYNTAX INTEGER
    ACCESS read-only
    STATUS mandatory
    DESCRIPTION "Number of handoff timeouts encountered by this node."
    ::= {dhtEntry 2}

nodeGetsTotal OBJECT-TYPE
    SYNTAX INTEGER
    ACCESS read-write
    STATUS mandatory
    DESCRIPTION "Number of GET operations coordinated by vnodes on this node since node was started."
    ::= { dhtEntry 3 }

nodePutsTotal OBJECT-TYPE
    SYNTAX INTEGER
    ACCESS read-write
    STATUS mandatory
    DESCRIPTION "Number of PUT operations coordinated by vnodes on this node since node was started."
    ::= { dhtEntry 4 }

cpuAvg15 OBJECT-TYPE
    SYNTAX INTEGER
    ACCESS read-write
    STATUS mandatory
    DESCRIPTION "The average number of active processes for the last 15 minutes."
    ::= { dhtEntry 5 }

nodeGetFsmTimeMedian OBJECT-TYPE
    SYNTAX OCTET STRING
    ACCESS read-write
    STATUS mandatory
    DESCRIPTION "Mean time between reception of client GET request and subsequent response to client."
    ::= { dhtEntry 6 }

nodePutFsmTimeMedian OBJECT-TYPE
    SYNTAX OCTET STRING
    ACCESS read-write
    STATUS mandatory
    DESCRIPTION "Mean time between reception of client PUT request and subsequent response to client."
    ::= { dhtEntry 7 }

dhtStatus OBJECT-TYPE
    SYNTAX RowStatus
    ACCESS  read-write
    STATUS  mandatory
    DESCRIPTION "The status of this row."
    ::= { dhtEntry 8 }


END
