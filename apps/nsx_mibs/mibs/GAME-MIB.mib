GAME-MIB DEFINITIONS ::= BEGIN

IMPORTS
    enterprises, IpAddress, OBJECT-TYPE
	FROM SNMPv2-SMI
    DisplayString
	FROM SNMPv2-TC
    RowStatus
    FROM STANDARD-MIB;

paynet OBJECT IDENTIFIER ::= { enterprises 88888 }

gameTable OBJECT-TYPE
    SYNTAX SEQUENCE OF GameEntry
    ACCESS not-accessible
    STATUS mandatory
    DESCRIPTION "Table of Game servers information."
    ::= { paynet 2 }

gameEntry OBJECT-TYPE
    SYNTAX GameEntry
    ACCESS not-accessible
    STATUS mandatory
    DESCRIPTION        "An entry in gameTable"
    INDEX   { gName }    ::= { gameTable 1 }

GameEntry ::= SEQUENCE {
    gName DisplayString,
    online INTEGER,
    gStatus RowStatus}

gName OBJECT-TYPE
    SYNTAX DisplayString
    ACCESS read-only
    STATUS mandatory
    DESCRIPTION "Game server name. Used as index for gameTable."
    ::= { gameEntry 1 }

online OBJECT-TYPE
    SYNTAX INTEGER
    ACCESS  read-write
    STATUS  mandatory
    DESCRIPTION "online users"
    ::= { gameEntry 2 }

gStatus OBJECT-TYPE
    SYNTAX RowStatus
    ACCESS  read-write
    STATUS  mandatory
     DESCRIPTION "The status of this row."
    ::= { gameEntry 3 }

END
